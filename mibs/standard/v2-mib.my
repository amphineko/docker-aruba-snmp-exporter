-- ArubaOS 8.11.2.0_87947
SNMPv2-MIB DEFINITIONS ::= BEGIN

IMPORTS
    MODULE-IDENTITY, OBJECT-TYPE, NOTIFICATION-TYPE,
    TimeTicks, Counter32, snmpModules, mib-2
        FROM SNMPv2-SMI
    DisplayString, TestAndIncr, TimeStamp                                 
        FROM SNMPv2-TC
    wlsxAuthFailIp
        FROM SNMPARUBA-SYSTEMEXT
    MODULE-COMPLIANCE, OBJECT-GROUP
        FROM SNMPv2-CONF;


snmpMIB MODULE-IDENTITY
    LAST-UPDATED "9510110000Z"                                            
    ORGANIZATION "IETF SNMPv2 Working Group"
    CONTACT-INFO
            "        Marshall T. Rose

             Postal: Dover Beach Consulting, Inc.
                     420 Whisman Court
                     Mountain View, CA  94043-2186
                     US

                Tel: +1 415 968 1052

             E-mail: mrose@dbc.mtview.ca.us"                              
    DESCRIPTION
            "The MIB module for SNMPv2 entities."
    REVISION      "9304010000Z"                                           
    DESCRIPTION
            "The initial revision of this MIB module was published as
            RFC 1450."
    ::= { snmpModules 1 }


snmpMIBObjects OBJECT IDENTIFIER ::= { snmpMIB 1 }

--  ::= { snmpMIBObjects 1 }        this OID is obsolete                  
--  ::= { snmpMIBObjects 2 }        this OID is obsolete                  
--  ::= { snmpMIBObjects 3 }        this OID is obsolete                  














-- the System group
--
-- a collection of objects common to all managed systems.

system   OBJECT IDENTIFIER ::= { mib-2 1 }

sysDescr OBJECT-TYPE
    SYNTAX      DisplayString (SIZE (0..255))
    MAX-ACCESS  read-only
    STATUS      current
    DESCRIPTION
            "A textual description of the entity.  This value should
            include the full name and version identification of the
            system's hardware type, software operating-system, and
            networking software."
    ::= { system 1 }

sysObjectID OBJECT-TYPE
    SYNTAX      OBJECT IDENTIFIER
    MAX-ACCESS  read-only
    STATUS      current
    DESCRIPTION
            "The vendor's authoritative identification of the network
            management subsystem contained in the entity.  This value is
            allocated within the SMI enterprises subtree (1.3.6.1.4.1)
            and provides an easy and unambiguous means for determining
            `what kind of box' is being managed.  For example, if vendor
            `Flintstones, Inc.' was assigned the subtree
            1.3.6.1.4.1.4242, it could assign the identifier
            1.3.6.1.4.1.4242.1.1 to its `Fred Router'."
    ::= { system 2 }

sysUpTime OBJECT-TYPE
    SYNTAX      TimeTicks
    MAX-ACCESS  read-only
    STATUS      current
    DESCRIPTION
            "The time (in hundredths of a second) since the network
            management portion of the system was last re-initialized."
    ::= { system 3 }

sysContact OBJECT-TYPE
    SYNTAX      DisplayString (SIZE (0..255))
    MAX-ACCESS  read-write
    STATUS      current











    DESCRIPTION
            "The textual identification of the contact person for this
            managed node, together with information on how to contact
            this person.  If no contact information is known, the value
            is the zero-length string."
    ::= { system 4 }

sysName OBJECT-TYPE
    SYNTAX      DisplayString (SIZE (0..255))
    MAX-ACCESS  read-write
    STATUS      current
    DESCRIPTION
            "An administratively-assigned name for this managed node.
            By convention, this is the node's fully-qualified domain
            name.  If the name is unknown, the value is the zero-length
            string."
    ::= { system 5 }

sysLocation OBJECT-TYPE
    SYNTAX      DisplayString (SIZE (0..255))
    MAX-ACCESS  read-write
    STATUS      current
    DESCRIPTION
            "The physical location of this node (e.g., `telephone
            closet, 3rd floor').  If the location is unknown, the value
            is the zero-length string."
    ::= { system 6 }

sysServices OBJECT-TYPE
    SYNTAX      INTEGER (0..127)
    MAX-ACCESS  read-only
    STATUS      current
    DESCRIPTION
            "A value which indicates the set of services that this
            entity may potentially offers.  The value is a sum.  This
            sum initially takes the value zero, Then, for each layer, L,
            in the range 1 through 7, that this node performs
            transactions for, 2 raised to (L - 1) is added to the sum.
            For example, a node which performs only routing functions
            would have a value of 4 (2^(3-1)).  In contrast, a node
            which is a host offering application services would have a
            value of 72 (2^(4-1) + 2^(7-1)).  Note that in the context
            of the Internet suite of protocols, values should be
            calculated accordingly:












                 layer      functionality
                   1        physical (e.g., repeaters)
                   2        datalink/subnetwork (e.g., bridges)
                   3        internet (e.g., supports the IP)
                   4        end-to-end  (e.g., supports the TCP)
                   7        applications (e.g., supports the SMTP)

            For systems including OSI protocols, layers 5 and 6 may also
            be counted."
    ::= { system 7 }


-- object resource information
--
-- a collection of objects which describe the SNMPv2 entity's
-- (statically and dynamically configurable) support of
-- various MIB modules.

sysORLastChange OBJECT-TYPE
    SYNTAX     TimeStamp
    MAX-ACCESS read-only
    STATUS     current
    DESCRIPTION
            "The value of sysUpTime at the time of the most recent
            change in state or value of any instance of sysORID."
    ::= { system 8 }

sysORTable OBJECT-TYPE
    SYNTAX     SEQUENCE OF SysOREntry
    MAX-ACCESS not-accessible
    STATUS     current
    DESCRIPTION
            "The (conceptual) table listing the capabilities of the
            local SNMPv2 entity acting in an agent role with respect to
            various MIB modules.  SNMPv2 entities having dynamically-
            configurable support of MIB modules will have a
            dynamically-varying number of conceptual rows."
    ::= { system 9 }


















sysOREntry OBJECT-TYPE
    SYNTAX     SysOREntry
    MAX-ACCESS not-accessible
    STATUS     current
    DESCRIPTION
            "An entry (conceptual row) in the sysORTable."
    INDEX      { sysORIndex }
    ::= { sysORTable 1 }

SysOREntry ::= SEQUENCE {
    sysORIndex     INTEGER,
    sysORID        OBJECT IDENTIFIER,
    sysORDescr     DisplayString,
    sysORUpTime    TimeStamp
}

sysORIndex OBJECT-TYPE
    SYNTAX     INTEGER (1..2147483647)
    MAX-ACCESS not-accessible
    STATUS     current
    DESCRIPTION
            "The auxiliary variable used for identifying instances of
            the columnar objects in the sysORTable."
    ::= { sysOREntry 1 }

sysORID OBJECT-TYPE
    SYNTAX     OBJECT IDENTIFIER
    MAX-ACCESS read-only
    STATUS     current
    DESCRIPTION
            "An authoritative identification of a capabilities statement
            with respect to various MIB modules supported by the local
            SNMPv2 entity acting in an agent role."
    ::= { sysOREntry 2 }

sysORDescr OBJECT-TYPE
    SYNTAX     DisplayString
    MAX-ACCESS read-only
    STATUS     current
    DESCRIPTION
            "A textual description of the capabilities identified by the
            corresponding instance of sysORID."
    ::= { sysOREntry 3 }













sysORUpTime OBJECT-TYPE
    SYNTAX     TimeStamp
    MAX-ACCESS read-only
    STATUS     current
    DESCRIPTION
            "The value of sysUpTime at the time this conceptual row was
            last instanciated."
    ::= { sysOREntry 4 }
















































-- the SNMP group                                                         
--
-- a collection of objects providing basic instrumentation and            
-- control of an SNMP entity.                                             

snmp     OBJECT IDENTIFIER ::= { mib-2 11 }                               

snmpInPkts OBJECT-TYPE                                                    
    SYNTAX     Counter32
    MAX-ACCESS read-only
    STATUS     current
    DESCRIPTION
            "The total number of messages delivered to the SNMP entity    
            from the transport service."                                  
    ::= { snmp 1 }                                                        

snmpInBadVersions OBJECT-TYPE                                             
    SYNTAX     Counter32                                                  
    MAX-ACCESS read-only                                                  
    STATUS     current                                                    
    DESCRIPTION                                                           
            "The total number of SNMP messages which were delivered to    
            the SNMP entity and were for an unsupported SNMP version."    
    ::= { snmp 3 }                                                        

snmpInBadCommunityNames OBJECT-TYPE                                       
    SYNTAX     Counter32
    MAX-ACCESS read-only
    STATUS     current
    DESCRIPTION
            "The total number of SNMP messages delivered to the SNMP      
            entity which used a SNMP community name not known to said     
            entity."                                                      
    ::= { snmp 4 }                                                        

snmpInBadCommunityUses OBJECT-TYPE                                        
    SYNTAX     Counter32                                                  
    MAX-ACCESS read-only                                                  
    STATUS     current                                                    
    DESCRIPTION                                                           
            "The total number of SNMP messages delivered to the SNMP      
            entity which represented an SNMP operation which was not      
            allowed by the SNMP community named in the message."          
    ::= { snmp 5 }                                                        












snmpInASNParseErrs OBJECT-TYPE                                            
    SYNTAX     Counter32
    MAX-ACCESS read-only
    STATUS     current
    DESCRIPTION
            "The total number of ASN.1 or BER errors encountered by the   
            SNMP entity when decoding received SNMP messages."            
    ::= { snmp 6 }                                                        

snmpEnableAuthenTraps OBJECT-TYPE                                         
    SYNTAX      INTEGER { enabled(1), disabled(2) }                       
    MAX-ACCESS  read-write                                                
    STATUS      current                                                   
    DESCRIPTION                                                           
            "Indicates whether the SNMP entity is permitted to generate   
            authenticationFailure traps.  The value of this object        
            overrides any configuration information; as such, it          
            provides a means whereby all authenticationFailure traps may  
            be disabled.                                                  

            Note that it is strongly recommended that this object be      
            stored in non-volatile memory so that it remains constant     
            across re-initializations of the network management system."  
    ::= { snmp 30 }                                                       

snmpSilentDrops OBJECT-TYPE                                               
    SYNTAX     Counter32
    MAX-ACCESS read-only
    STATUS     current
    DESCRIPTION
            "The total number of GetRequest-PDUs, GetNextRequest-PDUs,
            GetBulkRequest-PDUs, SetRequest-PDUs, and InformRequest-PDUs
            delivered to the SNMPv2 entity which were silently dropped
            because the size of a reply containing an alternate
            Response-PDU with an empty variable-bindings field was
            greater than either a local constraint or the maximum
            message size associated with the originator of the request."
    ::= { snmp 31 }                                                       


















snmpProxyDrops OBJECT-TYPE                                                
    SYNTAX     Counter32
    MAX-ACCESS read-only
    STATUS     current
    DESCRIPTION
            "The total number of GetRequest-PDUs, GetNextRequest-PDUs,
            GetBulkRequest-PDUs, SetRequest-PDUs, and InformRequest-PDUs
            delivered to the SNMPv2 entity which were silently dropped
            because the transmission of the (possibly translated)
            message to a proxy target failed in a manner (other than a
            time-out) such that no Response-PDU could be returned."
    ::= { snmp 32 }                                                       












































-- information for notifications                                          
--
-- a collection of objects which allow the SNMPv2 entity, when            
-- acting in an agent role, to be configured to generate
-- SNMPv2-Trap-PDUs.

snmpTrap       OBJECT IDENTIFIER ::= { snmpMIBObjects 4 }


snmpTrapOID OBJECT-TYPE
    SYNTAX     OBJECT IDENTIFIER
    MAX-ACCESS accessible-for-notify
    STATUS     current
    DESCRIPTION
            "The authoritative identification of the notification         
            currently being sent.  This variable occurs as the second     
            varbind in every SNMPv2-Trap-PDU and InformRequest-PDU."      
    ::= { snmpTrap 1 }

--  ::= { snmpTrap 2 }   this OID is obsolete                             

snmpTrapEnterprise OBJECT-TYPE
    SYNTAX     OBJECT IDENTIFIER
    MAX-ACCESS accessible-for-notify
    STATUS     current
    DESCRIPTION
            "The authoritative identification of the enterprise
            associated with the trap currently being sent.  When a
            SNMPv2 proxy agent is mapping an RFC1157 Trap-PDU into a
            SNMPv2-Trap-PDU, this variable occurs as the last varbind."
    ::= { snmpTrap 3 }

--  ::= { snmpTrap 4 }   this OID is obsolete                             























-- well-known traps                                                       

snmpTraps      OBJECT IDENTIFIER ::= { snmpMIBObjects 5 }

coldStart NOTIFICATION-TYPE                                               
    STATUS  current
    DESCRIPTION
            "A coldStart trap signifies that the SNMPv2 entity, acting
            in an agent role, is reinitializing itself and that its
            configuration may have been altered."
    ::= { snmpTraps 1 }

warmStart NOTIFICATION-TYPE
    STATUS  current
    DESCRIPTION
            "A warmStart trap signifies that the SNMPv2 entity, acting
            in an agent role, is reinitializing itself such that its
            configuration is unaltered."
    ::= { snmpTraps 2 }

-- Note the linkDown NOTIFICATION-TYPE ::= { snmpTraps 3 }
-- and the linkUp NOTIFICATION-TYPE ::= { snmpTraps 4 }
-- are defined in RFC 1573

authenticationFailure NOTIFICATION-TYPE
    OBJECTS { wlsxAuthFailIp }
    STATUS  current
    DESCRIPTION
            "An authenticationFailure trap signifies that the SNMPv2
            entity, acting in an agent role, has received a protocol
            message that is not properly authenticated.  While all
            implementations of the SNMPv2 must be capable of generating
            this trap, the snmpEnableAuthenTraps object indicates         
            whether this trap will be                                     
            generated."
    ::= { snmpTraps 5 }

-- Note the egpNeighborLoss NOTIFICATION-TYPE ::= { snmpTraps 6 }
-- is defined in RFC 1213


















-- the set group
--
-- a collection of objects which allow several cooperating
-- SNMPv2 entities, all acting in a manager role, to
-- coordinate their use of the SNMPv2 set operation.

snmpSet        OBJECT IDENTIFIER ::= { snmpMIBObjects 6 }


snmpSetSerialNo OBJECT-TYPE
    SYNTAX     TestAndIncr
    MAX-ACCESS read-write
    STATUS     current
    DESCRIPTION
            "An advisory lock used to allow several cooperating SNMPv2
            entities, all acting in a manager role, to coordinate their
            use of the SNMPv2 set operation.

            This object is used for coarse-grain coordination.  To
            achieve fine-grain coordination, one or more similar objects
            might be defined within each MIB group, as appropriate."
    ::= { snmpSet 1 }


































-- conformance information

snmpMIBConformance
               OBJECT IDENTIFIER ::= { snmpMIB 2 }

snmpMIBCompliances
               OBJECT IDENTIFIER ::= { snmpMIBConformance 1 }
snmpMIBGroups  OBJECT IDENTIFIER ::= { snmpMIBConformance 2 }


-- compliance statements

--    ::= { snmpMIBCompliances 1 }      this OID is obsolete              

snmpBasicCompliance MODULE-COMPLIANCE                                     
    STATUS  current
    DESCRIPTION
            "The compliance statement for SNMPv2 entities which
            implement the SNMPv2 MIB."
    MODULE  -- this module
        MANDATORY-GROUPS { snmpGroup, snmpSetGroup, systemGroup,          
                           snmpBasicNotificationsGroup }                  

        GROUP   snmpCommunityGroup
        DESCRIPTION
            "This group is mandatory for SNMPv2 entities which            
            support community-based authentication."                      

    ::= { snmpMIBCompliances 2 }                                          



























-- units of conformance                                                   

--  ::= { snmpMIBGroups 1 }           this OID is obsolete                
--  ::= { snmpMIBGroups 2 }           this OID is obsolete                
--  ::= { snmpMIBGroups 3 }           this OID is obsolete                
--  ::= { snmpMIBGroups 4 }           this OID is obsolete                

snmpGroup OBJECT-GROUP                                                    
    OBJECTS { snmpInPkts,                                                 
              snmpInBadVersions,                                          
              snmpInASNParseErrs,                                         
              snmpSilentDrops,                                            
              snmpProxyDrops,                                             
              snmpEnableAuthenTraps }                                     
    STATUS  current
    DESCRIPTION
            "A collection of objects providing basic instrumentation and  
            control of an SNMPv2 entity."                                 
    ::= { snmpMIBGroups 8 }                                               

snmpCommunityGroup OBJECT-GROUP
    OBJECTS { snmpInBadCommunityNames,                                    
              snmpInBadCommunityUses }                                    
    STATUS  current
    DESCRIPTION
            "A collection of objects providing basic instrumentation of
            a SNMPv2 entity which supports community-based
            authentication."
    ::= { snmpMIBGroups 9 }                                               

snmpSetGroup OBJECT-GROUP                                                 
    OBJECTS { snmpSetSerialNo }
    STATUS  current
    DESCRIPTION
            "A collection of objects which allow several cooperating
            SNMPv2 entities, all acting in a manager role, to coordinate
            their use of the SNMPv2 set operation."
    ::= { snmpMIBGroups 5 }


















systemGroup OBJECT-GROUP
    OBJECTS { sysDescr, sysObjectID, sysUpTime,
              sysContact, sysName, sysLocation,
              sysServices,
              sysORLastChange, sysORID,
              sysORUpTime, sysORDescr }
    STATUS  current
    DESCRIPTION
            "The system group defines objects which are common to all
            managed systems."
    ::= { snmpMIBGroups 6 }

-- snmpBasicNotificationsGroup NOTIFICATION-GROUP
--     NOTIFICATIONS { coldStart, authenticationFailure }
--     STATUS        current
--     DESCRIPTION
--             "The two notifications which an SNMPv2 entity is required to
--             implement."
--     ::= { snmpMIBGroups 7 }





































-- definitions in RFC 1213 made obsolete by the inclusion of a            
-- subset of the snmp group in this MIB                                   

snmpOutPkts OBJECT-TYPE                                                   
    SYNTAX      Counter32                                                 
    MAX-ACCESS  read-only                                                 
    STATUS      obsolete                                                  
    DESCRIPTION                                                           
            "The total number of SNMP Messages which were                 
            passed from the SNMP protocol entity to the                   
            transport service."                                           
    ::= { snmp 2 }                                                        

-- { snmp 7 } is not used                                                 

snmpInTooBigs OBJECT-TYPE                                                 
    SYNTAX      Counter32                                                 
    MAX-ACCESS  read-only                                                 
    STATUS      obsolete                                                  
    DESCRIPTION                                                           
            "The total number of SNMP PDUs which were                     
            delivered to the SNMP protocol entity and for                 
            which the value of the error-status field is                  
            `tooBig'."                                                    
    ::= { snmp 8 }                                                        

snmpInNoSuchNames OBJECT-TYPE                                             
    SYNTAX      Counter32                                                 
    MAX-ACCESS  read-only                                                 
    STATUS      obsolete                                                  
    DESCRIPTION                                                           
            "The total number of SNMP PDUs which were                     
            delivered to the SNMP protocol entity and for                 
            which the value of the error-status field is                  
            `noSuchName'."                                                
    ::= { snmp 9 }                                                        

snmpInBadValues OBJECT-TYPE                                               
    SYNTAX      Counter32                                                 
    MAX-ACCESS  read-only                                                 
    STATUS      obsolete                                                  
    DESCRIPTION                                                           
            "The total number of SNMP PDUs which were                     
            delivered to the SNMP protocol entity and for                 
            which the value of the error-status field is                  











            `badValue'."                                                  
    ::= { snmp 10 }                                                       

snmpInReadOnlys OBJECT-TYPE                                               
    SYNTAX      Counter32                                                 
    MAX-ACCESS  read-only                                                 
    STATUS      obsolete                                                  
    DESCRIPTION                                                           
            "The total number valid SNMP PDUs which were                  
            delivered to the SNMP protocol entity and for                 
            which the value of the error-status field is                  
            `readOnly'.  It should be noted that it is a                  
            protocol error to generate an SNMP PDU which                  
            contains the value `readOnly' in the error-status             
            field, as such this object is provided as a means             
            of detecting incorrect implementations of the                 
            SNMP."                                                        
    ::= { snmp 11 }                                                       

snmpInGenErrs OBJECT-TYPE                                                 
    SYNTAX      Counter32                                                 
    MAX-ACCESS  read-only                                                 
    STATUS      obsolete                                                  
    DESCRIPTION                                                           
            "The total number of SNMP PDUs which were                     
            delivered to the SNMP protocol entity and for                 
            which the value of the error-status field is                  
            `genErr'."                                                    
    ::= { snmp 12 }                                                       

snmpInTotalReqVars OBJECT-TYPE                                            
    SYNTAX      Counter32                                                 
    MAX-ACCESS  read-only                                                 
    STATUS      obsolete                                                  
    DESCRIPTION                                                           
            "The total number of MIB objects which have been              
            retrieved successfully by the SNMP protocol entity            
            as the result of receiving valid SNMP Get-Request             
            and Get-Next PDUs."                                           
    ::= { snmp 13 }                                                       

snmpInTotalSetVars OBJECT-TYPE                                            
    SYNTAX      Counter32                                                 
    MAX-ACCESS  read-only                                                 
    STATUS      obsolete                                                  











    DESCRIPTION                                                           
            "The total number of MIB objects which have been              
            altered successfully by the SNMP protocol entity              
            as the result of receiving valid SNMP Set-Request             
            PDUs."                                                        
    ::= { snmp 14 }                                                       

snmpInGetRequests OBJECT-TYPE                                             
    SYNTAX      Counter32                                                 
    MAX-ACCESS  read-only                                                 
    STATUS      obsolete                                                  
    DESCRIPTION                                                           
            "The total number of SNMP Get-Request PDUs which              
            have been accepted and processed by the SNMP                  
            protocol entity."                                             
    ::= { snmp 15 }                                                       

snmpInGetNexts OBJECT-TYPE                                                
    SYNTAX      Counter32                                                 
    MAX-ACCESS  read-only                                                 
    STATUS      obsolete                                                  
    DESCRIPTION                                                           
            "The total number of SNMP Get-Next PDUs which have            
            been accepted and processed by the SNMP protocol              
            entity."                                                      
    ::= { snmp 16 }                                                       

snmpInSetRequests OBJECT-TYPE                                             
    SYNTAX      Counter32                                                 
    MAX-ACCESS  read-only                                                 
    STATUS      obsolete                                                  
    DESCRIPTION                                                           
            "The total number of SNMP Set-Request PDUs which              
            have been accepted and processed by the SNMP                  
            protocol entity."                                             
    ::= { snmp 17 }                                                       

snmpInGetResponses OBJECT-TYPE                                            
    SYNTAX      Counter32                                                 
    MAX-ACCESS  read-only                                                 
    STATUS      obsolete                                                  
    DESCRIPTION                                                           
            "The total number of SNMP Get-Response PDUs which             
            have been accepted and processed by the SNMP                  
            protocol entity."                                             











    ::= { snmp 18 }                                                       

snmpInTraps OBJECT-TYPE                                                   
    SYNTAX      Counter32                                                 
    MAX-ACCESS  read-only                                                 
    STATUS      obsolete                                                  
    DESCRIPTION                                                           
            "The total number of SNMP Trap PDUs which have                
            been accepted and processed by the SNMP protocol              
            entity."                                                      
    ::= { snmp 19 }                                                       

snmpOutTooBigs OBJECT-TYPE                                                
    SYNTAX      Counter32                                                 
    MAX-ACCESS  read-only                                                 
    STATUS      obsolete                                                  
    DESCRIPTION                                                           
            "The total number of SNMP PDUs which were                     
            generated by the SNMP protocol entity and for                 
            which the value of the error-status field is                  
            `tooBig.'"                                                    
    ::= { snmp 20 }                                                       

snmpOutNoSuchNames OBJECT-TYPE                                            
    SYNTAX      Counter32                                                 
    MAX-ACCESS  read-only                                                 
    STATUS      obsolete                                                  
    DESCRIPTION                                                           
            "The total number of SNMP PDUs which were                     
            generated by the SNMP protocol entity and for                 
            which the value of the error-status is                        
            `noSuchName'."                                                
    ::= { snmp 21 }                                                       

snmpOutBadValues OBJECT-TYPE                                              
    SYNTAX      Counter32                                                 
    MAX-ACCESS  read-only                                                 
    STATUS      obsolete                                                  
    DESCRIPTION                                                           
            "The total number of SNMP PDUs which were                     
            generated by the SNMP protocol entity and for                 
            which the value of the error-status field is                  
            `badValue'."                                                  
    ::= { snmp 22 }                                                       












-- { snmp 23 } is not used                                                

snmpOutGenErrs OBJECT-TYPE                                                
    SYNTAX      Counter32                                                 
    MAX-ACCESS  read-only                                                 
    STATUS      obsolete                                                  
    DESCRIPTION                                                           
            "The total number of SNMP PDUs which were                     
            generated by the SNMP protocol entity and for                 
            which the value of the error-status field is                  
            `genErr'."                                                    
    ::= { snmp 24 }                                                       

snmpOutGetRequests OBJECT-TYPE                                            
    SYNTAX      Counter32                                                 
    MAX-ACCESS  read-only                                                 
    STATUS      obsolete                                                  
    DESCRIPTION                                                           
            "The total number of SNMP Get-Request PDUs which              
            have been generated by the SNMP protocol entity."             
    ::= { snmp 25 }                                                       

snmpOutGetNexts OBJECT-TYPE                                               
    SYNTAX      Counter32                                                 
    MAX-ACCESS  read-only                                                 
    STATUS      obsolete                                                  
    DESCRIPTION                                                           
            "The total number of SNMP Get-Next PDUs which have            
            been generated by the SNMP protocol entity."                  
    ::= { snmp 26 }                                                       

snmpOutSetRequests OBJECT-TYPE                                            
    SYNTAX      Counter32                                                 
    MAX-ACCESS  read-only                                                 
    STATUS      obsolete                                                  
    DESCRIPTION                                                           
            "The total number of SNMP Set-Request PDUs which              
            have been generated by the SNMP protocol entity."             
    ::= { snmp 27 }                                                       

snmpOutGetResponses OBJECT-TYPE                                           
    SYNTAX      Counter32                                                 
    MAX-ACCESS  read-only                                                 
    STATUS      obsolete                                                  
    DESCRIPTION                                                           











            "The total number of SNMP Get-Response PDUs which             
            have been generated by the SNMP protocol entity."             
    ::= { snmp 28 }                                                       

snmpOutTraps OBJECT-TYPE                                                  
    SYNTAX      Counter32                                                 
    MAX-ACCESS  read-only                                                 
    STATUS      obsolete                                                  
    DESCRIPTION                                                           
            "The total number of SNMP Trap PDUs which have                
            been generated by the SNMP protocol entity."                  
    ::= { snmp 29 }                                                       

snmpObsoleteGroup OBJECT-GROUP                                            
    OBJECTS { snmpOutPkts, snmpInTooBigs, snmpInNoSuchNames,              
              snmpInBadValues, snmpInReadOnlys, snmpInGenErrs,            
              snmpInTotalReqVars, snmpInTotalSetVars,                     
              snmpInGetRequests, snmpInGetNexts, snmpInSetRequests,       
              snmpInGetResponses, snmpInTraps, snmpOutTooBigs,            
              snmpOutNoSuchNames, snmpOutBadValues, snmpOutGenErrs,       
              snmpOutGetRequests, snmpOutGetNexts, snmpOutSetRequests,    
              snmpOutGetResponses, snmpOutTraps }                         
    STATUS  obsolete                                                      
    DESCRIPTION                                                           
            "A collection of objects from RFC 1213 made obsolete by this  
            MIB."                                                         
    ::= { snmpMIBGroups 10 }                                              

END
